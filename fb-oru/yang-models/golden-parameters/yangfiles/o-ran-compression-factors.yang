module o-ran-compression-factors {
  yang-version 1.1;
  namespace "urn:o-ran:compression-factors:1.0";
  prefix "o-ran-compression-factors";


  organization "O-RAN Alliance";

  contact
    "www.o-ran.org";

  description
    "This module defines the module capabilities for
    the O-RAN Radio Unit U-Plane configuration.

    Copyright 2019 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2019-07-03" {
    description
      "version 1.1.0

      1) changes related to compression bitwidth presentation";

    reference "ORAN-WG4.M.0-v01.00";
  }

  revision "2019-02-04" {
    description
      "version 1.0.0

      1) imported model from xRAN
      2) changed namespace and reference from xran to o-ran";

    reference "ORAN-WG4.M.0-v01.00";
  }

  grouping compression-params {
    leaf compression-type {
      type enumeration {
        enum STATIC {
          description
            "Indicates that static compression method will be used (both compression and IQ bitwidth)";
        }
        enum DYNAMIC {
          description
            "Indicates that dynamic compression method will be used";
        }
      }
      mandatory true;
      description
        "Compression type that O-DU wants to be supported";
    }

// *********** TO BE REMOVED ***********
    leaf bitwidth {
      when "../compression-type = 'STATIC'";
      type uint8;
      status deprecated;
      description
        "Bitwidth to be used in compression";
    }
// *************************************

    choice compression-format {
      description
        "Choice of compression format for particular element";

      case no-compresison {
        description "Compression for beam weights is not supported.";
      }
      case block-floating-point {
        description "Block floating point compression and decompression is supported.";

        leaf exponent {
          type uint8 {
            range "4";
          }
          description "Exponent bit width size in number of bits used when encoding in udCompParam.";
        }
      }

      case block-scaling {
        description "Block scaling compression and decompresion is supported.";
        leaf block-scalar {
          type uint8;
            description
              "Common scaler for compressed PRB";
        }
      }

      case u-law {
        description "u-Law compression and decompresion method is supported.";
        leaf comp-bit-width {
          type uint8 {
            range "0..15";
          }
          description "Bit with for u-law compression";
        }
        leaf comp-shift {
          type uint8 {
            range "0..15";
          }
          description
            "the shift applied to the entire PRB";
        }
      }

      case beam-space-compression {
        description "Beamspace compression and decompression is supported. Applies to beamforming weights only.";
        leaf-list active-beam-space-coeficient-mask {
          type uint8;
          description
            "active beamspace coefficient indices associated with the compressed beamforming vector";
        }
        leaf block-scaler {
          type uint8;
          description
            "Common scaler for compressed beamforming coefficients";
        }
      }

      case modulation-compression {
        description "Modulation compression and decompression is supported.";
        leaf csf {
          type uint8 {
            range "0..1";
          }
          description "Constallation shift flag";
        }

        leaf mod-comp-scaler {
          type uint16 {
            range "0..32767";
          }
          description "Modulation compression scaler value.";
        }
      }
    }
  }

  grouping compression-details {
    description "";

    leaf iq-bitwidth {
      type uint8;
      description
        "Bitwidth to be used in compression";
    }

    uses compression-params;
  }
}
