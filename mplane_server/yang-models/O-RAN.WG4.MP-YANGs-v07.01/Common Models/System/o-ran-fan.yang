module o-ran-fan {
  yang-version 1.1;
  namespace "urn:o-ran:fan:1.0";
  prefix "o-ran-fan";


  organization "O-RAN Alliance";

  contact
    "www.o-ran.org";

  description
    "This module defines the state of the O-RAN equipment's fans.

    Copyright 2019 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2019-07-03" {
    description
      "version 1.1.0

      1) backward compatible changes to introduce groupings.";

    reference "ORAN-WG4.M.0-v01.00";
  }

  revision "2019-02-04" {
    description
      "version 1.0.0

      1) imported model from xRAN
      2) changed namespace and reference from xran to o-ran";

    reference "ORAN-WG4.M.0-v01.00";
  }

  typedef percent {
   type uint16 {
     range "0 .. 100";
   }
   description "Percentage";
  }

  grouping fan-grouping {
    description "a fan grouping";
    list fan-state {
      key name;
      description "a list of the fans based on their unique names";
      leaf name {
        type string {
          length "1..255";
        }
        description
          "A name that is unique that identifies a fan instance.
          This name may be used in fault management to refer to a fault source
          or affected object";
      }
      leaf fan-location {
        type uint8;
        description "A number indicating the location of the FAN in the fan tray";
      }
      leaf present-and-operating {
        type boolean;
        mandatory true;
        description
          "Indicates if a fan is present and operating in the location";
      }
      leaf vendor-code {
        when "../present-and-operating = 'true'";
        type uint8 {
          range "0..7";
        }
        description
          "Indicates fan vendor code. Fan vendors are detected with ID pins
          using 3 bits digital inputs.

          Optional node included when the NETCONF Server has determined
          the fan vendor code.";
      }
      leaf fan-speed {
        when "../present-and-operating = 'true'";
        type percent;
        description
          "Measured fan speed. Expressed as percentage of max fan speed.

          Optional node included when the fan speed can be measured.";
      }
      leaf target-speed {
        when "../present-and-operating = 'true'";
        type uint16;
        units rpm;
        description "the target speed of the fan";
      }
    }
  }

  container fan-tray {
    config false;
    description "top level tree covering off operational state of the fans";

    uses fan-grouping;
  }
}
