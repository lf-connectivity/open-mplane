module o-ran-udp-echo {
  yang-version 1.1;
  namespace "urn:o-ran:udpecho:1.0";
  prefix "o-ran-echo";

  import o-ran-interfaces {
    prefix "o-ran-int";
  }

  organization "O-RAN Alliance";

  contact
    "www.o-ran.org";

  description
    "This module covers off aspects of interface transport
    verification for UDP/IP based C/U plane connections based on UDP Echo.

    Copyright 2019 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2019-02-04" {
    description
      "version 1.0.0

      1) imported model from xRAN
      2) changed namespace and reference from xran to o-ran";

    reference "ORAN-WG4.M.0-v01.00";
  }

// groupings

  grouping udp-echo-group {
    description "a udp echo grouping";
    leaf enable-udp-echo {
      type boolean;
      default false;
      description
        "whether O-RU's UDP ech server is enabled";
    }

    leaf dscp-config {
      type enumeration {
        enum REFLECTIVE {
          description
            "DSCP in echoed datagrams is copied from received datagram";
        }
        enum EF {
          description
            "DSCP in echoed datagrams is always be set to expeditied
            forwarding Per Hop Behaviour.";
        }
      }
      default EF;
      description "configuration of UDP echo DSCP";
    }

    leaf echo-replies-transmitted {
      type uint32;
      config false;
      description
        "The total number of UDP echo replies transmitted by the O-RU.";
    }
  }

  container udp-echo {
    if-feature o-ran-int:UDPIP-BASED-CU-PLANE;
    description "container for udp echo";

    uses udp-echo-group;
  }
}
